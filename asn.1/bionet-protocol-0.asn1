-- Copyright (c) 2008-2010, Regents of the University of Colorado.
-- This work was supported by NASA contracts NNJ05HE10G, NNC06CB40C, and
-- NNC07CB47C.


BionetProtocol1
DEFINITIONS AUTOMATIC TAGS
::=
BEGIN

    -- 
    -- these are the fundamental data types of Bionet
    -- 

    ResourceFlavor ::= ENUMERATED {
        sensor(0),
        actuator,
        parameter
    }

    ResourceDataType ::= ENUMERATED {
        binary(0),
        uint8,
        int8,
        uint16,
        int16,
        uint32,
        int32,
        float,
        double,
        string
    }

    Value ::= CHOICE {
        binary-v   BOOLEAN,
        uint8-v    INTEGER (0..255),
        int8-v     INTEGER (-128..127),
        uint16-v   INTEGER (0..65535),
        int16-v    INTEGER (-32768..32767),
        uint32-v   INTEGER (0..4294967295),
        int32-v    INTEGER (-2147483648..2147483647),
        real       REAL,   -- this is used for both datatype "float" and "double"
        string     PrintableString
    }

    Datapoint ::= SEQUENCE {
        value       Value,
        timestamp   GeneralizedTime
    }

    Resource ::= SEQUENCE {
        id           PrintableString,
        flavor       ResourceFlavor,
        datatype     ResourceDataType,
        datapoints   SEQUENCE OF Datapoint
    }

    StreamDirection ::= ENUMERATED {
        producer(0),
        consumer
    }

    Stream ::= SEQUENCE {
        id         PrintableString,
        type       PrintableString,
        direction  StreamDirection
    }

    Node ::= SEQUENCE {
        id          PrintableString,
        resources   SEQUENCE OF Resource,
        streams     SEQUENCE OF Stream
    }

    HardwareAbstractor ::= SEQUENCE {
        type     PrintableString,
        id       PrintableString,
        nodes    SEQUENCE OF Node
    }

    


    -- 
    -- Helper structs
    -- 

    ResourceMetadata ::= SEQUENCE {
        nodeId       PrintableString,
        resourceId   PrintableString,
        flavor       ResourceFlavor,
        datatype     ResourceDataType
    }

    ResourceDatapoints ::= SEQUENCE {
        nodeId          PrintableString,
        resourceId      PrintableString,
        newDatapoints   SEQUENCE OF Datapoint
    }

    BDMPublishDatapoint ::= SEQUENCE {
        datapoint       Datapoint,
        timestamp       GeneralizedTime,
        entrySeq        INTEGER,
        bdmId           PrintableString
    }


    --
    -- Sent to Resource subscribers on new-node events
    --
    BDMResourceMetadata ::= SEQUENCE {
        habType      PrintableString,
        habId        PrintableString,
        nodeId       PrintableString,
        nodeUid      OCTET STRING, -- 64bit fingerprint of node. 
        resourceId   PrintableString,
        flavor       ResourceFlavor,
        datatype     ResourceDataType
    }


    -- 
    -- sent to Resource subscribers on new datapoints
    --
    BDMResourceDatapoints ::= SEQUENCE {
        nodeUid         OCTET STRING, -- 64bit fingerprint of node. 
        resourceId      PrintableString,
        newDatapointsBDM   SEQUENCE OF BDMPublishDatapoint
    }

    BDMNewLostNode ::= SEQUENCE {
        entrySeq  INTEGER,
	timestamp GeneralizedTime,
        bdmId     PrintableString,
        uid       OCTET STRING,  -- 64bit fingerprint of the node
        habType   PrintableString,
        habId     PrintableString,
        node      Node
    }

    BDMNewLostHab ::= SEQUENCE {
        entrySeq  INTEGER,
	timestamp GeneralizedTime,
        bdmId     PrintableString,
        habType   PrintableString,
        habId     PrintableString
    }

    -- 
    -- ResourceDatapointsQuery: request from a client to the bdm server to
    --     list Resource Datapoints within a time window
    --
    -- ResourceDatapointsReply: reply from the bdm server to a client
    --     providing all available, matching information
    -- 

    ResourceDatapointsQuery ::= SEQUENCE {
        habType              PrintableString,
        habId                PrintableString,
        nodeId               PrintableString,
        resourceId           PrintableString,
        datapointStartTime   GeneralizedTime,
        datapointEndTime     GeneralizedTime,
	entryStart           INTEGER,
	entryEnd             INTEGER
    }

    ResourceDatapointsReply ::= SEQUENCE {
        bdms             SEQUENCE OF DataManager,
	lastEntry        INTEGER
    }


    -- 
    -- SetResourceValue sets the value of a Resource, duh
    -- 
    -- Note: the value is a string, not a Value, because the sender of the
    --     message might not know the ResourceDataType
    --

    SetResourceValue ::= SEQUENCE {
        nodeId      PrintableString,
        resourceId  PrintableString,
        value       PrintableString
    }


    -- 
    -- StreamData contains some stream data
    -- 

    StreamData ::= SEQUENCE {
        nodeId    PrintableString,
        streamId  PrintableString,
        data      OCTET STRING
    }


    -- 
    -- C2H-Message is a Client-to-Hab message
    -- 

    C2H-Message ::= CHOICE {
        --subscribeNode         PrintableString,
        --subscribeDatapoints   PrintableString,
        setResourceValue      SetResourceValue,
        streamData            StreamData
    }


    -- 
    -- H2C-Message is a Hab-to-Client message
    -- 

    H2C-Message ::= CHOICE {
        newNode            Node,
        lostNode           PrintableString,
        resourceMetadata   ResourceMetadata,
        datapointsUpdate   ResourceDatapoints,
        streamData         StreamData
    }






    --
    -- BDM Client/Pub/Sub Messages
    --



    --
    -- BDM Client-to-Server messages
    --
    BDMSendState ::= SEQUENCE {
        seq             INTEGER,
        topic           PrintableString
    }

    BDM-C2S-Message ::= CHOICE {
        resourceDatapointsQuery ResourceDatapointsQuery,
        subscribeHab            PrintableString,
        subscribeNode           PrintableString,
        subscribeDatapoints     PrintableString,
	sendState               BDMSendState
    }


    --
    -- BDM Server-to-Client messages
    --

    BDM-S2C-Message ::= CHOICE {
        resourceDatapointsReply ResourceDatapointsReply,
        resourceMetadata        BDMResourceMetadata,
        datapointsUpdate        BDMResourceDatapoints,
        newHab                  BDMNewLostHab,
        lostHab                 BDMNewLostHab,
        newNode                 BDMNewLostNode,
        lostNode                BDMNewLostNode,
	sendState               BDMSendState
    }


    --
    -- BDM Sync Messages
    -- 
    
    -- 
    -- BDM Sync Metadata Messages
    -- 
    -- note: there will never be datapoints in a BDM Sync Metadata 
    -- message. They belong in the BDM Sync Update message.
    --

    -- An event that something happened
    -- This structure can hang off of any metadata element,
    --
    BDM-Event-Type ::= ENUMERATED {
        new(0),
        lost
    }
    -- NOTE: Logically, the bdm-id should be here, but we 
    -- Use the BDM as the top of the tree to pack more efficiently
    BDM-Event ::= SEQUENCE {
        timestamp       GeneralizedTime,
        entrySeq        INTEGER,
        type            BDM-Event-Type
    }

    BDM-Datapoint ::= SEQUENCE {
        datapoint   Datapoint,
        event       BDM-Event
    }

    BDM-Resource ::= SEQUENCE {
        id           PrintableString,
        flavor       ResourceFlavor,
        datatype     ResourceDataType,
        datapoints   SEQUENCE OF BDM-Datapoint
    }

    BDM-Node ::= SEQUENCE {
        id          PrintableString,
        uid         OCTET STRING,  -- 64bit fingerprint of the node
        resources   SEQUENCE OF BDM-Resource, -- There will never be datapoints for sync messages
        streams     SEQUENCE OF Stream,
        events      SEQUENCE OF BDM-Event
    }

    BDM-HardwareAbstractor ::= SEQUENCE {
        type     PrintableString,
        id       PrintableString,
        nodes    SEQUENCE OF BDM-Node,
        events   SEQUENCE OF BDM-Event
    }

    DataManager ::= SEQUENCE {
	id       PrintableString,
	hablist     SEQUENCE OF BDM-HardwareAbstractor
    }

    BDM-Sync-Metadata-Message ::= SEQUENCE OF DataManager


    --
    -- BDM Sync Datapoints Messages
    --
    -- note: the metadata associated with the datapoints needs to have
    -- already been received and processed before this message.
    --
    BDMSyncDatapoint ::= SEQUENCE {
        datapoint       Datapoint,
        timestamp       GeneralizedTime,
        entrySeq        INTEGER
    }

    ResourceRecord ::= SEQUENCE {
        resourceKey            OCTET STRING, -- The 64bit fingerprint
        resourceDatapoints     SEQUENCE OF BDMSyncDatapoint
    }

    BDMSyncRecord ::= SEQUENCE {
        bdmID            PrintableString,
        syncResources    SEQUENCE OF ResourceRecord
    }
    BDM-Sync-Datapoints-Message ::= SEQUENCE OF BDMSyncRecord





    -- BDM Sync Message
    -- this contains either a metadata message or a datapoints message
    BDM-Sync-Data ::= CHOICE {
        metadataMessage      BDM-Sync-Metadata-Message,
        datapointsMessage    BDM-Sync-Datapoints-Message,
	ackMetadata          INTEGER,
	ackDatapoints        INTEGER
    }

    BDM-Sync-Message ::= SEQUENCE {
        data         BDM-Sync-Data,
	syncchannel  INTEGER, -- A Sender-specific channel ID
        firstSeq     INTEGER,
        lastSeq      INTEGER
    }

END
